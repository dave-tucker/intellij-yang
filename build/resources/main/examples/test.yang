module acme-foo {
     namespace "http://acme.example.com/foo";
     prefix "acfoo";


     list interface {
         key "name";
         leaf name {
             type string;
         }

         leaf mtu {
             type uint32;
             description "The MTU of the interface.";
         }
     }
 }
